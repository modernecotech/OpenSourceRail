# FreeCAD macro: choose a generated city desktop-links.json, then open the selected object.
import importlib.util
from pathlib import Path
from PySide import QtWidgets
root = Path(__file__).resolve().parents[2]
spec = importlib.util.spec_from_file_location('osr_desktop_bridge', root / 'tools/integration/desktop_bridge.py')
bridge = importlib.util.module_from_spec(spec)
spec.loader.exec_module(bridge)
filename, _ = QtWidgets.QFileDialog.getOpenFileName(None, 'OSR city desktop-links.json', str(root / 'build/supervision'), '*.json')
if filename:
    bridge.freecad(filename)
